SMARTCTL-PLUS-MIB DEFINITIONS ::= BEGIN

-- https://github.com/gfvh/smartctlmon

-- imports and exports

IMPORTS
    OBJECT-TYPE, NOTIFICATION-TYPE, MODULE-IDENTITY,
    Integer32, Opaque, enterprises, Counter32
        FROM SNMPv2-SMI

    TEXTUAL-CONVENTION, DisplayString, TruthValue
        FROM SNMPv2-TC;

hacking MODULE-IDENTITY
	LAST-UPDATED 	"201710110000Z"
	ORGANIZATION 	"IT community"
	CONTACT-INFO	"IT Community"
	DESCRIPTION	"This MIB module forms the base for all SMARTCTL SNMP MIBs."
	REVISION     	"201710110000Z"
	DESCRIPTION	"Created SMARTCTL-PLUS-MIB.  Namespace declaration."
    ::= { enterprises 38696 }

-- Branches for registering other Hacking Network Solutions MIB modules:
hackingInternal		OBJECT IDENTIFIER ::= { hacking 1 }
hackingExperimental	OBJECT IDENTIFIER ::= { hacking 2 }
hackingStandard		OBJECT IDENTIFIER ::= { hacking 3 }

-- OID values assigned in the hackingExperimental branch:
-- smartCtlMIB		OBJECT IDENTIFIER ::= { hackingExperimental  1 } - SMARTCTL-MIB
-- mdRaidMIB		OBJECT IDENTIFIER ::= { hackingExperimental  2 } - MD-RAID-MIB
-- lvmMIB			OBJECT IDENTIFIER ::= { hackingExperimental  3 } - LVM-MIB



END
